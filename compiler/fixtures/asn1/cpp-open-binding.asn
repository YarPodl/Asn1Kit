M DEFINITIONS ::= BEGIN
  C ::= CLASS { &id OBJECT IDENTIFIER UNIQUE, &T } WITH SYNTAX { &T IDENTIFIED BY &id }
  NoData ::= NULL
  emptyEntry C ::= { NoData IDENTIFIED BY {1 2 3} }
  dataEntry C ::= { INTEGER (0..100) IDENTIFIED BY {1 2 4} }
  base C ::= { BOOLEAN IDENTIFIED BY {1 2 5} }
  access C ::= { NULL IDENTIFIED BY {1 2 6} }
  open-entries C ::= { BOOLEAN IDENTIFIED BY {1 2 7} }
  Mixed C ::= {emptyEntry | dataEntry | base | access | open-entries}
  AlgorithmIdentifier{C:S} ::= SEQUENCE {
    algorithm C.&id({S}), parameters C.&T({S}{@algorithm}) OPTIONAL }
  Extension{C:S} ::= SEQUENCE {
    extnID C.&id({S}),
    extnValue OCTET STRING (CONTAINING C.&T({S}{@extnID})) }
  Attribute{C:S} ::= SEQUENCE {
    type C.&id({S}),
    values SET OF C.&T({S}{@type}) }
  Holder ::= SEQUENCE {
    mixed AlgorithmIdentifier{Mixed},
    ext Extension{Mixed},
    attr Attribute{Mixed} }
  Outer ::= SEQUENCE {
    id OBJECT IDENTIFIER,
    nested SEQUENCE OF SEQUENCE {
      value C.&T({Mixed}{@id}) } }
END
