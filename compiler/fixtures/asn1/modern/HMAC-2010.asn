-- Extracted from RFC 6268; ASN.1 syntax retained.
-- Copyright (c) The IETF Trust and the persons identified as authors.
-- See LICENSE.txt for the Simplified BSD license.

  HMAC-2010  { iso(1) identified-organization(3) dod(6) internet(1)
     security(5) mechanisms(5) pkix(7) mod(0) id-mod-hmac(74) }
  DEFINITIONS EXPLICIT TAGS ::=
  BEGIN
    EXPORTS ALL;

    IMPORTS

    MAC-ALGORITHM, SMIME-CAPS
    FROM AlgorithmInformation-2009
      { iso(1) identified-organization(3) dod(6) internet(1) security(5)
        mechanisms(5) pkix(7) id-mod(0)
        id-mod-algorithmInformation-02(58)};

    --
    --  This object set contains all of the MAC algorithms that are
    --    defined in this module.
    --  One would add it to a constraining set of objects such as the
    --    MessageAuthenticationCodeAlgorithmSet in [RFC5652]
    --

    MessageAuthAlgs MAC-ALGORITHM ::= {
      maca-hMAC-SHA224 |
      maca-hMAC-SHA256 |
      maca-hMAC-SHA384 |
      maca-hMAC-SHA512
    }

    --
    --  This object set contains all of the S/MIME capabilities that
    --     have been defined for all the MAC algorithms in this module.
    --  One would add this to an object set that is used to restrict
    --    S/MIME capabilities such as the SMimeCapsSet variable in
    --    RFC 3851 (obsoleted by RFC 5751) as modified in RFC 5911.
    --

    SMimeCaps SMIME-CAPS ::= {
      maca-hMAC-SHA224.&smimeCaps     |
      maca-hMAC-SHA256.&smimeCaps     |
      maca-hMAC-SHA384.&smimeCaps     |
      maca-hMAC-SHA512.&smimeCaps
    }

    --
    --  Define the base OID for the algorithm identifiers
    --







    rsadsi OBJECT IDENTIFIER ::=
         {iso(1) member-body(2) us(840) rsadsi(113549)}

    digestAlgorithm   OBJECT IDENTIFIER ::= {rsadsi 2}

    --
    --  Define the necessary algorithm identifiers
    --

    id-hmacWithSHA224 OBJECT IDENTIFIER ::= {digestAlgorithm 8}
    id-hmacWithSHA256 OBJECT IDENTIFIER ::= {digestAlgorithm 9}
    id-hmacWithSHA384 OBJECT IDENTIFIER ::= {digestAlgorithm 10}
    id-hmacWithSHA512 OBJECT IDENTIFIER ::= {digestAlgorithm 11}

    --
    --  Define each of the MAC-ALGORITHM objects to describe the
    --    algorithms defined
    --

    maca-hMAC-SHA224 MAC-ALGORITHM ::= {
      IDENTIFIER id-hmacWithSHA224
      PARAMS TYPE NULL ARE preferredPresent
      IS-KEYED-MAC TRUE
      SMIME-CAPS {IDENTIFIED BY id-hmacWithSHA224}
    }


    maca-hMAC-SHA256 MAC-ALGORITHM ::= {
      IDENTIFIER id-hmacWithSHA256
      PARAMS TYPE NULL ARE preferredPresent
      IS-KEYED-MAC TRUE
      SMIME-CAPS {IDENTIFIED BY id-hmacWithSHA256}
    }


    maca-hMAC-SHA384 MAC-ALGORITHM ::= {
      IDENTIFIER id-hmacWithSHA384
      PARAMS TYPE NULL ARE preferredPresent
      IS-KEYED-MAC TRUE
      SMIME-CAPS {IDENTIFIED BY id-hmacWithSHA384}
    }












    maca-hMAC-SHA512 MAC-ALGORITHM ::= {
      IDENTIFIER id-hmacWithSHA512
      PARAMS TYPE NULL ARE preferredPresent
      IS-KEYED-MAC TRUE
      SMIME-CAPS {IDENTIFIED BY id-hmacWithSHA512}
    }

  END
